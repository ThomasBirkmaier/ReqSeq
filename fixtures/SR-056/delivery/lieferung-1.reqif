# Lastenheft 2026-11

## REQ-1: Measure the wind
The station measures the wind speed.
- Priority: High

## REQ-2: Show the wind
The display shows the wind speed.
- Priority: Low
- satisfies -> REQ-1

## REQ-3: Store the wind
The station stores the wind speed.
- Priority: Low

## REQ-4: Send the wind
The station sends the wind speed.
- Priority: Low
