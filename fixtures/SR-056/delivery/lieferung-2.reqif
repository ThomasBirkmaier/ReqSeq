# Lastenheft 2026-12

## REQ-1: Measure the wind
The station measures the wind speed every 10 s.
- Priority: High

## REQ-2: Show the wind
The display shows the wind speed.
- Priority: Low
- satisfies -> REQ-1

## REQ-3: Store the wind
The station stores the wind speed for 30 days.
- Priority: Low

## REQ-5: Warn of storms
The station warns above 20 m/s.
- Priority: High
- satisfies -> REQ-1
