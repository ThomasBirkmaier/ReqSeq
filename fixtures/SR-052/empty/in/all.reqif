# Weather station

# Specification: Weather station

## R1: Measure with an anemometer (Decision)
We use a cup anemometer.
- status: approved
- reqseq-values: {"status":"approved","title":"Measure with an anemometer"}

## R2: Know the weather (Need)
The operator wants to know the weather.
- status: approved
- reqseq-markdown: The operator wants to *know* the weather.
- reqseq-values: {"status":"approved","title":"Know the weather"}

## R3: Stage 6 (Package)
- status: draft
- reqseq-values: {"status":"draft","title":"Stage 6"}

## R4: Show wind speed & gusts <live> (System Requirement)
Wind
The station shows the current wind speed in m/s:
- average over 10 s
- peak over 3 s
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| Value | Unit |
| --- | --- |
| speed | m/s |
- rationale: Operators **need** it.
- requirement-type: performance
- acceptance-criteria:
  - Given wind, when it blows, then the *speed* shows within 1 s.
  - Given a gust, then the peak shows for 10 s.
- validity: VAR-0052c1
- packages: PKG-0052f1
- emergent: no
- verification-method: test
- topic: Display
- status: approved
- reqseq-markdown: # Wind

  The station shows the **current** wind speed in m/s:

  - average over 10 s
  - peak over 3 s

  ![Anemometer](SR-0000000052a1/anemometer.png)

  | Value | Unit |
  | --- | --- |
  | speed | m/s |
- reqseq-values: {"status":"approved","title":"Show wind speed & gusts <live>","requirement-type":"performance","acceptance-criteria":["Given wind, when it blows, then the *speed* shows within 1 s.","Given a gust, then the peak shows for 10 s."],"verification-method":"test","emergent":"no","rationale":"Operators **need** it.","topic":"Display","validity":[{"id":"52052052-0000-4000-8000-0000000052c1","version":"n1:67ebd0624004c969","title":"Coast"}],"packages":[{"id":"52052052-0000-4000-8000-0000000052f1","version":"n1:67ebd0624004c969","title":"Stage 6"}],"derives-from":[{"id":"52052052-0000-4000-8000-0000000052d1","version":"n1:99370531eef49776","title":"Know the weather"}],"based-on":[{"id":"52052052-0000-4000-8000-0000000052e1","version":"n1:c3e5587a8d1b230f","title":"Measure with an anemometer"}]}
- Derives from -> R2
- Based on -> R1
- Validity -> R7
- Package -> R3

## R5: Store wind history (System Requirement)
The station keeps the wind speed of the last 24 h.
- requirement-type: functional
- packages: PKG-0052f1
- status: draft
- reqseq-values: {"status":"draft","title":"Store wind history","requirement-type":"functional","packages":[{"id":"52052052-0000-4000-8000-0000000052f1","version":"n1:67ebd0624004c969","title":"Stage 6"}],"refines":[{"id":"52052052-0000-4000-8000-0000000052a1","version":"n1:584cedef0a756936","title":"Show wind speed & gusts <live>"},{"id":"52052052-0000-4000-8000-0000000052a3","version":"n1:9de1cddc22503560","title":"Measure temperature"}],"derives-from":[{"id":"52052052-0000-4000-8000-0000000052ff","version":"n1:0000000000000000"}]}
- Refines -> R4
- Refines -> R6
- Derives from -> R8
- Package -> R3

## R6: Measure temperature (System Requirement)
The station measures the air temperature.
- requirement-type: functional
- status: draft
- reqseq-values: {"status":"draft","title":"Measure temperature","requirement-type":"functional"}

## R7: Coast (Variant)
- status: draft
- reqseq-values: {"status":"draft","title":"Coast"}

## R8 (missing)
