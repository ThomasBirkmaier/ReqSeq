# Lastenheft 2026-11

# Specification: Lastenheft

## HEAD-1: Wind (Heading)

### REQ-1: Measure the wind (Customer Requirement)
The station shall measure the wind speed.
Every 10 s.
- Priority: High
- Internal Comment: check with team
- satisfies -> HEAD-1

### REQ-2: Show the wind (Customer Requirement)
The display shows the wind speed.
- Priority: Low
- satisfies -> REQ-1
