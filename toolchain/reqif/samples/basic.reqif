# Customer A
Hand-written sample

# Specification: Requirements

## A-1 & more: Start (Requirement)
The system shall start.
- Effort: 5
- Weight: 0.5
- Due: 2026-11-01T00:00:00Z
- Safety: true
- Priority: High

### req-2 (Requirement)
- Refines -> A-1 & more

# Specification: Appendix

## note-1 (Note)
- Note text: Only a note
- Refines -> A-1 & more
